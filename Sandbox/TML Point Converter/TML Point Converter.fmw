FME workspace TML Point Converter.fmw

Parameters:
- Output_Format = OGCKML
- SourceDataset_CSV2_3 = C:\Users\pnmorris\OneDrive - Terracon Consultants Inc\Desktop\Local FME Workflows\TML\TML\Coal Creek Boring Locations.TML   # Source TML Point File(s)

Readers:
- CSV2_1: CSV2 from $(SourceDataset_CSV2_3) in EPSG:4326

Writers:
- GENERIC_1: GENERIC to C:\Users\pnmorris\OneDrive - Terracon Consultants Inc\Desktop\Local FME Workflows\TML\Point\Output

CSV (reader CSV2_1)
    attributes: col0 string, col1 string, col2 string, col3 string
    -> StringReplacer
StringReplacer
    CASE = NO
    FIND_TEXT = [a-zA-Z,=+]*
    NO_MATCH = _FME_NO_OP_
    REGEXP = YES
    SRC_ATTRS = col0
    -> StringReplacer_2
StringReplacer_2
    CASE = NO
    FIND_TEXT = Îž
    NO_MATCH = _FME_NO_OP_
    REGEXP = YES
    REPLACE_TEXT = ,
    SRC_ATTRS = col0
    -> AttributeSplitter
AttributeSplitter
    ATTR_NAME = col0
    DELIMITER = ,
    DROP_EMPTY_PARTS = Yes
    LIST_NAME = _coordinate_list
    TRIM_OPTION = Both
    -> AttributeCreator
AttributeCreator
    ATTR_TABLE:
      SET_TO Longitude = @Value(_coordinate_list{1})
      SET_TO Latitude = @Value(_coordinate_list{0})
    -> VertexCreator
VertexCreator
    MEASURE_TYPE = Continuous
    MISSING_VAL_MODE = Compute
    MODE_NAME = Add Point
    XVAL = @Value(Longitude)
    YVAL = @Value(Latitude)
    -> StringReplacer_3
StringReplacer_3
    CASE = NO
    FIND_TEXT = Îž
    NO_MATCH = _FME_NO_OP_
    REGEXP = NO
    REPLACE_TEXT = " "
    SRC_ATTRS = col0,col1,col2,col3,fme_feature_type,Latitude,Longitude
    -> Converted_TML (writer GENERIC_1)
Converted_TML (writer GENERIC_1)
    attributes: Longitude varchar(200), Latitude varchar(200), col1 buffer, col2 buffer, col3 buffer
