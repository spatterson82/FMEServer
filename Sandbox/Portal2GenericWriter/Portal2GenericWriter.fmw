FME workspace Portal2GenericWriter.fmw

Parameters:
- SourceDataset_ARCGISPORTALFEATURES = https://geodata.terracon.com/portal/   # Portal URL
- DestDataset_GENERIC = C:\Users\pnmorris\OneDrive - Terracon Consultants Inc\Desktop\Local FME Workflows\Generic_Writer\Output   # Destination Generic (Any Format) Folder
- Output_Format = FILEGDB

Readers:
- ARCGISPORTALFEATURES_1: ARCGISPORTALFEATURES from $(SourceDataset_ARCGISPORTALFEATURES)

Writers:
- GENERIC_1: GENERIC to $(DestDataset_GENERIC)

MS_Sampling_Locations (reader ARCGISPORTALFEATURES_1)
    attributes: objectid esriFieldTypeOID, sampling_status esriFieldTypeString(2048), cooler_status esriFieldTypeString(2048), cooler_status_date_time esriFieldTypeDate, pws_id esriFieldTypeString(2048), system_name esriFieldTypeString(2048), principal_county_served esriFieldTypeString(2048), number_of_entry_points esriFieldTypeString(2048), gw_gui_sources_to_sample esriFieldTypeString(200), sw_sources_to_sample___tbd esriFieldTypeString(200), contact_person_for_pfas_samplin esriFieldTypeString(2048), email_of_contact_person esriFieldTypeString(2048), phone___of_contact_person esriFieldTypeString(200), shipping_address_to_receive_sam esriFieldTypeString(2048), updated_cooler_drop_off_address esriFieldTypeString(200), geocode_address esriFieldTypeString(2048), comment esriFieldTypeString(2048), longitude esriFieldTypeString(2048), latitude esriFieldTypeString(2048), do_you_have_the_ability_to_coll esriFieldTypeString(200), office esriFieldTypeString(2048), route esriFieldTypeString(2048), planned_start_date esriFieldTypeString(2048), edd_received esriFieldTypeDate, edd_processed esriFieldTypeDate, created_user esriFieldTypeString(255), created_date esriFieldTypeDate, last_edited_user esriFieldTypeString(255), last_edited_date esriFieldTypeDate, globalid esriFieldTypeGlobalID(38),
      number_coolers_dropped_off esriFieldTypeInteger, cooler_pickup_datetime esriFieldTypeDate, cooler_recd_by_lab esriFieldTypeDate, comments esriFieldTypeString(1000), fire_district_id esriFieldTypeString(20), fire_district_name esriFieldTypeString(255), fs_groundwater_wells esriFieldTypeString(255), last_edited_user_og esriFieldTypeString(255), last_edited_date_og esriFieldTypeDate
    -> DateTimeStamper
DateTimeStamper
    DATETIME_ATTR = _timestamp
    INCLUDE_OFFSET = NO
    STAMP_TYPE = datetime
    TIMEZONE = local
    -> DateTimeConverter
DateTimeConverter
    DATETIME_ATTR = _timestamp
    OUT_FORMAT = %Y%m%d_%H%M
    PASSTHROUGH = NO
    REPAIR_INPUT = YES
    -> TestFilter
TestFilter
    DEFAULT_VALUE = Not Null
    TEST_LIST = "BOOL_OP,OR,COMPOSITE_TEST,""""""1"""""",TEST_CLAUSE,TEST cooler_status ATTRIBUTE_VALUE_NULL """,Null
    Not Null -> AttributeFilter
AttributeFilter
    ATTR_NAME = cooler_status
    ATTR_VALUES = <Empty>,<Missing>,<Null>,<Unfiltered>,D,P,PU,RL,PP,C,NR,CD
    D -> AttributeCreator_2
    P -> AttributeCreator
    PU -> AttributeCreator_3
    RL -> AttributeCreator_4
    PP -> AttributeCreator_5
    C -> AttributeCreator_6
    NR -> AttributeCreator_7
    CD -> AttributeCreator_8
AttributeCreator_2
    ATTR_TABLE = SET_TO cooler_status = Dropped Off
    -> AttributeManager
AttributeCreator
    ATTR_TABLE = SET_TO cooler_status = Prepared
    -> AttributeManager
AttributeCreator_3
    ATTR_TABLE = SET_TO cooler_status = Picked Up
    -> AttributeManager
AttributeCreator_4
    ATTR_TABLE = SET_TO cooler_status = Received by Lab
    -> AttributeManager
AttributeCreator_5
    ATTR_TABLE = SET_TO cooler_status = Postponed
    -> AttributeManager
AttributeCreator_6
    ATTR_TABLE = SET_TO cooler_status = Canceled
    -> AttributeManager
AttributeCreator_7
    ATTR_TABLE = SET_TO cooler_status = No Response
    -> AttributeManager
AttributeCreator_8
    ATTR_TABLE = SET_TO cooler_status = Contacted
    -> AttributeManager
AttributeManager
    ATTR_TABLE:
      RENAME_SET_VALUE cooler_pickup_datetime
      RENAME_SET_VALUE cooler_recd_by_lab > cooler_recd_by_lab_datetime
      RENAME_SET_VALUE cooler_status_date_time > cooler_dropoff_date_time
      REMOVE last_edited_user_og
      REMOVE last_edited_date_og
    -> MS_Sampling_Locations_Test (writer GENERIC_1)
MS_Sampling_Locations_Test (writer GENERIC_1)
    attributes: pws_id varchar(2048), system_name varchar(2048), cooler_status varchar(2048), number_coolers_dropped_off int32, cooler_pickup_datetime datetime, cooler_recd_by_lab_datetime datetime, cooler_dropoff_date_time datetime, principal_county_served varchar(2048), number_of_entry_points varchar(2048), gw_gui_sources_to_sample varchar(200), sw_sources_to_sample___tbd varchar(200), contact_person_for_pfas_samplin varchar(2048), email_of_contact_person varchar(2048), phone___of_contact_person varchar(200), shipping_address_to_receive_sam varchar(2048), updated_cooler_drop_off_address varchar(200), geocode_address varchar(2048), comment varchar(2048), longitude varchar(2048), latitude varchar(2048), do_you_have_the_ability_to_coll varchar(200), office varchar(2048), route varchar(2048), planned_start_date varchar(2048), edd_received datetime, edd_processed datetime, created_user varchar(255), created_date datetime, last_edited_user varchar(255), last_edited_date datetime,
      globalid varchar(38), sampling_status varchar(2048), _timestamp buffer, comments varchar(1000), fire_district_id varchar(20), fire_district_name varchar(255), fs_groundwater_wells varchar(255)
